BACS2-MIB DEFINITIONS ::= BEGIN

   IMPORTS
      MODULE-IDENTITY, OBJECT-TYPE, NOTIFICATION-TYPE,
      OBJECT-IDENTITY, Counter32, Gauge32, Integer32
         FROM SNMPv2-SMI
      DisplayString, TimeStamp, AutonomousType, TEXTUAL-CONVENTION
         FROM SNMPv2-TC
      MODULE-COMPLIANCE, OBJECT-GROUP
         FROM SNMPv2-CONF;

   --
   -- BACS2 Settings
   --

   bacsSettings MODULE-IDENTITY 
      LAST-UPDATED "202101260845Z"
      ORGANIZATION "Generex Computergesellschaft mbH"
      CONTACT-INFO "info@generex.de"
      DESCRIPTION  "BACS information"
      REVISION "202101260845Z"
      DESCRIPTION "added MODULE-IDENTITY statement, removed duplicate bacsNumStrings entry, removed further syntax errors"
   ::= { bacs2 1 }

   PositiveInteger ::= TEXTUAL-CONVENTION
       DISPLAY-HINT "d"
       STATUS       current
       DESCRIPTION
               "This data type is a non-zero and non-negative value."
       SYNTAX       INTEGER (1..2147483647)

   NonNegativeInteger ::= TEXTUAL-CONVENTION
       DISPLAY-HINT "d"
       STATUS       current
       DESCRIPTION
               "This data type is a non-negative value."
       SYNTAX       INTEGER (0..2147483647)

   org         OBJECT IDENTIFIER ::= { iso 3 }  --  "iso" = 1
   dod         OBJECT IDENTIFIER ::= { org 6 }
   internet    OBJECT IDENTIFIER ::= { dod 1 }
   mgmt        OBJECT IDENTIFIER ::= { internet 2 }
   mib-2       OBJECT IDENTIFIER ::= { mgmt 1 }
   upsMIB      OBJECT IDENTIFIER ::= { mib-2 33 }
   bacs2       OBJECT IDENTIFIER ::= { upsMIB 5 }

   bacsModuleType OBJECT-TYPE
       SYNTAX      INTEGER {
           c20     (0),
           c21     (1),
           c30     (10),
           c40     (20),
           c41     (21)
       }
       MAX-ACCESS  read-only
       STATUS      current
       DESCRIPTION "BACS Module Type. (0=C20, 1=C21, 10=C30, 20=C40, 21=C41)"
       ::= { bacsSettings 1 }

   bacsNumStrings OBJECT-TYPE
       SYNTAX      NonNegativeInteger
       UNITS       "strings"
       MAX-ACCESS  read-only
       STATUS      current
       DESCRIPTION "Number of battery strings."
       ::= { bacsSettings 2 }

   bacsNumBatteries OBJECT-TYPE
       SYNTAX      NonNegativeInteger
       UNITS       "batteries"
       MAX-ACCESS  read-only
       STATUS      current
       DESCRIPTION "Total number of batteries."
       ::= { bacsSettings 3 }

   bacsBattCap OBJECT-TYPE
       SYNTAX      PositiveInteger
       UNITS       "Ah"
       MAX-ACCESS  read-only
       STATUS      current
       DESCRIPTION "Capacity of installed batteries."
       ::= { bacsSettings 4 }

   bacsImpcLowAlarm OBJECT-TYPE
       SYNTAX      PositiveInteger
       UNITS       "0.01 mOhm"
       MAX-ACCESS  read-write
       STATUS      current
       DESCRIPTION "Impedance low alarm level."
       ::= { bacsSettings 8 }

   bacsImpcHighAlarm OBJECT-TYPE
       SYNTAX      PositiveInteger
       UNITS       "0.01 mOhm"
       MAX-ACCESS  read-write
       STATUS      current
       DESCRIPTION "Impedance high alarm level."
       ::= { bacsSettings 9 }

   bacsTemperatureLowAlarm OBJECT-TYPE
       SYNTAX      Integer32
       UNITS       "0.1 deg of current temperature unit"
       MAX-ACCESS  read-write
       STATUS      current
       DESCRIPTION "Temperature alarm below this level."
       ::= { bacsSettings 10 }

   bacsTemperatureHighAlarm OBJECT-TYPE
       SYNTAX      Integer32
       UNITS       "0.1 deg of current temperature unit"
       MAX-ACCESS  read-write
       STATUS      current
       DESCRIPTION "Temperature alarm above this level."
       ::= { bacsSettings 11 }

   bacsVoltageLowAlarm OBJECT-TYPE
       SYNTAX      PositiveInteger
       UNITS       "0.01 volt"
       MAX-ACCESS  read-write
       STATUS      current
       DESCRIPTION "Voltage alarm below this level."
       ::= { bacsSettings 12 }

   bacsVoltageHighAlarm OBJECT-TYPE
       SYNTAX      PositiveInteger
       UNITS       "0.01 volt"
       MAX-ACCESS  read-write
       STATUS      current
       DESCRIPTION "Voltage alarm above this level."
       ::= { bacsSettings 13 }

   bacsImpcLowWarn OBJECT-TYPE
       SYNTAX      PositiveInteger
       UNITS       "0.01 mOhm"
       MAX-ACCESS  read-write
       STATUS      current
       DESCRIPTION "Impedance low warning level."
       ::= { bacsSettings 14 }

   bacsImpcHighWarn OBJECT-TYPE
       SYNTAX      PositiveInteger
       UNITS       "0.01 mOhm"
       MAX-ACCESS  read-write
       STATUS      current
       DESCRIPTION "Impedance high warning level."
       ::= { bacsSettings 15 }

   bacsTemperatureLowWarn OBJECT-TYPE
       SYNTAX      Integer32
       UNITS       "0.1 deg of current temperature unit"
       MAX-ACCESS  read-write
       STATUS      current
       DESCRIPTION "Temperature warning below this level."
       ::= { bacsSettings 16 }

   bacsTemperatureHighWarn OBJECT-TYPE
       SYNTAX      Integer32
       UNITS       "0.1 deg of current temperature unit"
       MAX-ACCESS  read-write
       STATUS      current
       DESCRIPTION "Temperature warning above this level."
       ::= { bacsSettings 17 }

   bacsVoltageLowWarn OBJECT-TYPE
       SYNTAX      PositiveInteger
       UNITS       "0.01 volt"
       MAX-ACCESS  read-write
       STATUS      current
       DESCRIPTION "Voltage warning below this level."
       ::= { bacsSettings 18 }

   bacsVoltageHighWarn OBJECT-TYPE
       SYNTAX      PositiveInteger
       UNITS       "0.01 volt"
       MAX-ACCESS  read-write
       STATUS      current
       DESCRIPTION "Voltage warning above this level."
       ::= { bacsSettings 19 }

   bacsTemperatureUnit OBJECT-TYPE
       SYNTAX      INTEGER {
           celsius     (0),
           fahrenheit     (1)
       }
       MAX-ACCESS  read-write
       STATUS      current
       DESCRIPTION "Temperature unit currently in use. (0=Celsius, 1=Fahrenheit)"
       ::= { bacsSettings 20 }

   bacsStringVoltageLowAlarm OBJECT-TYPE
       SYNTAX      PositiveInteger
       UNITS       "0.01 volt"
       MAX-ACCESS  read-write
       STATUS      current
       DESCRIPTION "String Voltage alarm below this level."
       ::= { bacsSettings 21 }

   bacsStringVoltageHighAlarm OBJECT-TYPE
       SYNTAX      PositiveInteger
       UNITS       "0.01 volt"
       MAX-ACCESS  read-write
       STATUS      current
       DESCRIPTION "String Voltage alarm above this level."
       ::= { bacsSettings 22 }

   bacsStringVoltageLowWarn OBJECT-TYPE
       SYNTAX      PositiveInteger
       UNITS       "0.01 volt"
       MAX-ACCESS  read-write
       STATUS      current
       DESCRIPTION "String Voltage warning below this level."
       ::= { bacsSettings 23 }

   bacsStringVoltageHighWarn OBJECT-TYPE
       SYNTAX      PositiveInteger
       UNITS       "0.01 volt"
       MAX-ACCESS  read-write
       STATUS      current
       DESCRIPTION "String Voltage warning above this level."
       ::= { bacsSettings 24 }

   bacsStringCurrentDeviationDischargeAlarm OBJECT-TYPE
       SYNTAX      PositiveInteger
       UNITS       "0.01 A"
       MAX-ACCESS  read-write
       STATUS      current
       DESCRIPTION "String Current Deviation alarm above this level, during discharge."
       ::= { bacsSettings 25 }

   bacsStringCurrentDeviationChargeAlarm OBJECT-TYPE
       SYNTAX      PositiveInteger
       UNITS       "0.01 A"
       MAX-ACCESS  read-write
       STATUS      current
       DESCRIPTION "String Current Deviation alarm above this level, during charge."
       ::= { bacsSettings 26 }

   bacsStringCurrentDeviationDischargeWarn OBJECT-TYPE
       SYNTAX      PositiveInteger
       UNITS       "0.01 A"
       MAX-ACCESS  read-write
       STATUS      current
       DESCRIPTION "String Current Deviation warning above this level, during discharge."
       ::= { bacsSettings 27 }

   bacsStringCurrentDeviationChargeWarn OBJECT-TYPE
       SYNTAX      PositiveInteger
       UNITS       "0.01 A"
       MAX-ACCESS  read-write
       STATUS      current
       DESCRIPTION "String Current Deviation warning above this level, during charge."
       ::= { bacsSettings 28 }

   --
   -- BACS Objects
   --

   bacsObjects   OBJECT IDENTIFIER ::= { bacs2 2 }

   bacsStatus OBJECT-TYPE
       SYNTAX      PositiveInteger
       UNITS       "HEX flags"
       MAX-ACCESS  read-only
       STATUS      current
       DESCRIPTION "BACS System Status Flags."
       ::= { bacsObjects 1 }

  bacsAvModuleVolt OBJECT-TYPE
      SYNTAX      PositiveInteger
      UNITS       "0.01 Volt"
      MAX-ACCESS  read-only
      STATUS      current
      DESCRIPTION "Average module voltage."
      ::= { bacsObjects 2 }

  bacsTotalVolt OBJECT-TYPE
      SYNTAX      PositiveInteger
      UNITS       "0.01 Volt"
      MAX-ACCESS  read-only
      STATUS      current
      DESCRIPTION "Total voltage of all modules."
      ::= { bacsObjects 3 }

   bacsNumModules OBJECT-TYPE
       SYNTAX      NonNegativeInteger
       MAX-ACCESS  read-only
       STATUS      current
       DESCRIPTION "The number of installed battery modules."
       ::= { bacsObjects 4 }

   BacsEntry ::= SEQUENCE {
       bacsModuleIndex         PositiveInteger,
       bacsModuleVoltage       PositiveInteger,
       bacsModuleTemperature   Integer32,
       bacsModuleBypass        NonNegativeInteger,
       bacsModuleResistance    NonNegativeInteger,
       bacsModuleState         NonNegativeInteger,
       bacsModuleChargeLevel   NonNegativeInteger
   }

   bacsModuleTable    OBJECT-TYPE
       SYNTAX      SEQUENCE OF BacsEntry
       MAX-ACCESS  not-accessible
       STATUS      current
       DESCRIPTION "The list of battery table entries."
       ::= { bacsObjects 5 }

   bacsModuleEntry  OBJECT-TYPE
       SYNTAX      BacsEntry
       MAX-ACCESS  not-accessible
       STATUS      current
       DESCRIPTION "An entry containing information applicable to a particular battery."
       INDEX       { bacsModuleIndex }
       ::= { bacsModuleTable 1 }

   bacsModuleIndex OBJECT-TYPE
       SYNTAX      PositiveInteger
       MAX-ACCESS  not-accessible
       STATUS      current
       DESCRIPTION "The module identifier."
       ::= { bacsModuleEntry 1 }

   bacsModuleVoltage OBJECT-TYPE
       SYNTAX      PositiveInteger
       UNITS       "0.01 volt"
       MAX-ACCESS  read-only
       STATUS      current
       DESCRIPTION "The module voltage."
       ::= { bacsModuleEntry 2 }

   bacsModuleTemperature OBJECT-TYPE
       SYNTAX      Integer32
       UNITS       "0.1 degrees of current temperature unit"
       MAX-ACCESS  read-only
       STATUS      current
       DESCRIPTION "The module temperature."
       ::= { bacsModuleEntry 3 }

   bacsModuleBypass OBJECT-TYPE
       SYNTAX      NonNegativeInteger
       UNITS       "0.1 percent"
       MAX-ACCESS  read-only
       STATUS      current
       DESCRIPTION "The module bypass voltage."
       ::= { bacsModuleEntry 4 }

   bacsModuleResistance OBJECT-TYPE
       SYNTAX      NonNegativeInteger
       UNITS       "0.01 mOhm"
       MAX-ACCESS  read-only
       STATUS      current
       DESCRIPTION "The module impedance."
       ::= { bacsModuleEntry 5 }

   bacsModuleState OBJECT-TYPE
       SYNTAX      NonNegativeInteger
       MAX-ACCESS  read-only
       STATUS      current
       DESCRIPTION "The module alarm flags(0x0=No Alarm, 0x1=General Alarm, 0x2=System Failure, 0x4=Voltage High Alarm, 0x8=Voltage Low Alarm, 0x10=Temperature High Alarm, 0x20=Temperature Low Alarm, 0x40=Resistor High Alarm, 0x80=Resistor Low Alarm, 0x100=Equalizing Error Alarm, 0x200=Voltage High Warning, 0x400=Voltage Low Warning, 0x800=Temperature High Warning, 0x1000=Temperature Low Warning, 0x2000=Resistor High Warning, 0x4000=Resistor Low Warning, 0x8000=Incompatible Module Rev)."
       ::= { bacsModuleEntry 6 }

   bacsModuleChargeLevel OBJECT-TYPE
       SYNTAX      NonNegativeInteger
       MAX-ACCESS  read-only
       STATUS      current
       DESCRIPTION "The battery charge level reported by the module"
       ::= { bacsModuleEntry 7 }

   bacsNumStrings2 OBJECT-TYPE
       SYNTAX      NonNegativeInteger
       MAX-ACCESS  read-only
       STATUS      current
       DESCRIPTION "The number of installed battery strings."
       ::= { bacsObjects 6 }

   StringEntry ::= SEQUENCE {
       bacsStringIndex         PositiveInteger,
       bacsStringCurrent       PositiveInteger,
       bacsStringTotalVolt     PositiveInteger,
       bacsStringAverageVolt   PositiveInteger,
       bacsStringCurrentAC     PositiveInteger,
       bacsStringAlarm         NonNegativeInteger,
       bacsStringAlarm2        NonNegativeInteger
   }

   bacsStringTable    OBJECT-TYPE
       SYNTAX      SEQUENCE OF StringEntry
       MAX-ACCESS  not-accessible
       STATUS      current
       DESCRIPTION "The list of stringy table entries."
       ::= { bacsObjects 7 }

   bacsStringEntry  OBJECT-TYPE
       SYNTAX      StringEntry
       MAX-ACCESS  not-accessible
       STATUS      current
       DESCRIPTION "An entry containing information applicable to a particular string of batteries."
       INDEX       { bacsStringIndex }
       ::= { bacsStringTable 1 }

   bacsStringIndex OBJECT-TYPE
       SYNTAX      PositiveInteger
       MAX-ACCESS  not-accessible
       STATUS      current
       DESCRIPTION "The string identifier."
       ::= { bacsStringEntry 1 }

   bacsStringCurrent OBJECT-TYPE
       SYNTAX      PositiveInteger
       UNITS       "0.01 ampere"
       MAX-ACCESS  read-only
       STATUS      current
       DESCRIPTION "The string current."
       ::= { bacsStringEntry 2 }

   bacsStringTotalVolt OBJECT-TYPE
       SYNTAX      PositiveInteger
       UNITS       "0.01 volt"
       MAX-ACCESS  read-only
       STATUS      current
       DESCRIPTION "The string total voltage."
       ::= { bacsStringEntry 3 }

   bacsStringAverageVolt OBJECT-TYPE
       SYNTAX      PositiveInteger
       UNITS       "0.01 volt"
       MAX-ACCESS  read-only
       STATUS      current
       DESCRIPTION "The string average voltage per battery."
       ::= { bacsStringEntry 4 }

   bacsStringCurrentAC OBJECT-TYPE
       SYNTAX      PositiveInteger
       UNITS       "0.01 ampere"
       MAX-ACCESS  read-only
       STATUS      current
       DESCRIPTION "The string AC current."
       ::= { bacsStringEntry 5 }

   bacsStringAlarm OBJECT-TYPE
       SYNTAX      NonNegativeInteger
       UNITS       "HEX flags"
       MAX-ACCESS  read-only
       STATUS      current
       DESCRIPTION "The BACS String Alarm Flags(0x0=No Alarm, 0x1=General Alarm, 0x2=System Failure, 0x4=Voltage High Alarm, 0x8=Voltage Low Alarm, 0x10=Temperature High Alarm, 0x20=Temperature Low Alarm, 0x40=Resistor High Alarm, 0x80=Resistor Low Alarm, 0x100=Equalizing Error Alarm, 0x200=Voltage High Warning, 0x400=Voltage Low Warning, 0x800=Temperature High Warning, 0x1000=Temperature Low Warning, 0x2000=Resistor High Warning, 0x4000=Resistor Low Warning, 0x8000=Incompatible Module Rev)."
       ::= { bacsStringEntry 6 }

   bacsStringAlarm2 OBJECT-TYPE
       SYNTAX      NonNegativeInteger
       UNITS       "HEX flags"
       MAX-ACCESS  read-only
       STATUS      current
       DESCRIPTION "The BACS String Alarm2 Flags(0x0=No Alarm, 0x1=Current Sensor High, 0x2=Current Sensor Low, 0x4=Current Sensor High Warning, 0x8=Current Sensor Low Warning, 0x10=Equalizing Cut Off, 0x20=Current Deviation Discharge, 0x40=Current Deviation Charge, 0x80=Current Deviation Discharge Warning, 0x100=Current Deviation Charge Warning)."
       ::= { bacsStringEntry 7 }

   --
   -- BACS Alarms
   --

   bacsAlarms   OBJECT IDENTIFIER ::= { bacs2 3 }

   bacsAlarmsPresent OBJECT-TYPE
       SYNTAX      Gauge32
       MAX-ACCESS  read-only
       STATUS      current
       DESCRIPTION "The present number of active alarm conditions."
       ::= { bacsAlarms 1 }

   bacsAlarmTable OBJECT-TYPE
       SYNTAX      SEQUENCE OF BacsAlarm
       MAX-ACCESS  not-accessible
       STATUS      current
       DESCRIPTION "A list of alarm entries."
       ::= { bacsAlarms 2 }

   bacsAlarmEntry OBJECT-TYPE
       SYNTAX      BacsAlarm
       MAX-ACCESS  not-accessible
       STATUS      current
       DESCRIPTION "An entry containing information applicable to a particular alarm."
       INDEX      { bacsAlarmId }
       ::= { bacsAlarmTable 1 }

   BacsAlarm ::= SEQUENCE {
       bacsAlarmId          PositiveInteger,
       bacsAlarmDescr       AutonomousType,
       bacsAlarmTime        TimeStamp
   }

   bacsAlarmId OBJECT-TYPE
       SYNTAX      PositiveInteger
       MAX-ACCESS  read-only
       STATUS      current
       DESCRIPTION "A unique identifier for an alarm condition. This value must remain constant."
       ::= { bacsAlarmEntry 1 }

   bacsAlarmDescr OBJECT-TYPE
       SYNTAX      AutonomousType
       MAX-ACCESS  read-only
       STATUS      current
       DESCRIPTION "A reference to an alarm description object. The object referenced should not be
                 accessible, but rather be used to provide a unique description of the alarm condition."
       ::= { bacsAlarmEntry 2 }

   bacsAlarmTime OBJECT-TYPE
       SYNTAX      TimeStamp
       MAX-ACCESS  read-only
       STATUS      current
       DESCRIPTION "The value of sysUpTime when the alarm condition was detected. If the alarm
               condition was detected at the time of agent startup and presumably existed before
               agent startup, the value of dcAlarmTime shall equal 0."
       ::= { bacsAlarmEntry 3 }

   bacsWellKnownAlarms OBJECT IDENTIFIER ::= { bacsAlarms 3 }

   bacsAlarmSystemError OBJECT-IDENTITY
       STATUS      current
       DESCRIPTION "This object indicates a communication problem from the agent to one or more of the battery modules."
       ::= { bacsWellKnownAlarms  1 }

   bacsAlarmResistWarn OBJECT-IDENTITY
       STATUS      current
       DESCRIPTION "This object indicates that the internal restiance of one or more batteries is above the warning level."
       ::= { bacsWellKnownAlarms  2 }

   bacsAlarmResistAlarm OBJECT-IDENTITY
       STATUS      current
       DESCRIPTION "This object indicates that the internal restiance of one or more batteries is above the alarm level."
       ::= { bacsWellKnownAlarms  3 }

   bacsAlarmVoltage OBJECT-IDENTITY
       STATUS      current
       DESCRIPTION "This object indicates that the voltage of one or more batteries is outside the defined rage."
       ::= { bacsWellKnownAlarms  4 }

   bacsAlarmTemperature OBJECT-IDENTITY
       STATUS      current
       DESCRIPTION "This object indicates that the temperature of one or more batteries is outside the defined range."
       ::= { bacsWellKnownAlarms  5 }

   bacsAlarmVoltageHigh OBJECT-IDENTITY
       STATUS      current
       DESCRIPTION "This object indicates that the voltage of one or more batteries is higher than the defined range."
       ::= { bacsWellKnownAlarms  6 }

   bacsAlarmVoltageLow OBJECT-IDENTITY
       STATUS      current
       DESCRIPTION "This object indicates that the voltage of one or more batteries is lower than the defined range."
       ::= { bacsWellKnownAlarms  7 }

   bacsAlarmTemperatureHigh OBJECT-IDENTITY
       STATUS      current
       DESCRIPTION "This object indicates that the temperature of one or more batteries is higher than the defined range."
       ::= { bacsWellKnownAlarms  8 }

   bacsAlarmTemperatureLow OBJECT-IDENTITY
       STATUS      current
       DESCRIPTION "This object indicates that the temperature of one or more batteries is lower than the defined range."
       ::= { bacsWellKnownAlarms  9 }

   bacsAlarmResistAlarmHigh OBJECT-IDENTITY
       STATUS      current
       DESCRIPTION "This object indicates that the internal restiance of one or more batteries is above the alarm level."
       ::= { bacsWellKnownAlarms  10 }

   bacsAlarmResistAlarmLow OBJECT-IDENTITY
       STATUS      current
       DESCRIPTION "This object indicates that the internal restiance of one or more batteries is below the alarm level."
       ::= { bacsWellKnownAlarms  11 }

   bacsAlarmEqualizing OBJECT-IDENTITY
       STATUS      current
       DESCRIPTION "This object indicates that there is an error with Equalizing."
       ::= { bacsWellKnownAlarms  12 }

   bacsAlarmVoltageWarnHigh OBJECT-IDENTITY
       STATUS      current
       DESCRIPTION "This object indicates that the voltage of one or more batteries is higher than the defined warning range."
       ::= { bacsWellKnownAlarms  13 }

   bacsAlarmVoltageWarnLow OBJECT-IDENTITY
       STATUS      current
       DESCRIPTION "This object indicates that the voltage of one or more batteries is lower than the defined warning range."
       ::= { bacsWellKnownAlarms  14 }

   bacsAlarmTemperatureWarnHigh OBJECT-IDENTITY
       STATUS      current
       DESCRIPTION "This object indicates that the Temperature of one or more batteries is higher than the defined warning range."
       ::= { bacsWellKnownAlarms  15 }

   bacsAlarmTemperatureWarnLow OBJECT-IDENTITY
       STATUS      current
       DESCRIPTION "This object indicates that the Temperature of one or more batteries is lower than the defined warning range."
       ::= { bacsWellKnownAlarms  16 }

   bacsAlarmResistWarnHigh OBJECT-IDENTITY
       STATUS      current
       DESCRIPTION "This object indicates that the internal restiance of one or more batteries is higher than the defined warning range."
       ::= { bacsWellKnownAlarms  17 }

   bacsAlarmResistWarnLow OBJECT-IDENTITY
       STATUS      current
       DESCRIPTION "This object indicates that the internal restiance of one or more batteries is lower than the defined warning range."
       ::= { bacsWellKnownAlarms  18 }

    bacsAlarmInitializing OBJECT-IDENTITY
       STATUS      current
       DESCRIPTION "Bacs Alarm Initializing ."
       ::= { bacsWellKnownAlarms  19 }

    bacsAlarmCommunicationLost OBJECT-IDENTITY
       STATUS      current
       DESCRIPTION "Bacs Alarm Communication Lost ."
       ::= { bacsWellKnownAlarms  20 }

    bacsAlarmBatteryBreakerOpen OBJECT-IDENTITY
       STATUS      current
       DESCRIPTION "Bacs Alarm Battery Breaker Open ."
       ::= { bacsWellKnownAlarms  21 }

    bacsAlarmThermalRunaway OBJECT-IDENTITY
       STATUS      current
       DESCRIPTION "Bacs Alarm Thermal Runaway."
       ::= { bacsWellKnownAlarms  22 }

    bacsAlarmSensorCommunicationLost OBJECT-IDENTITY
       STATUS      current
       DESCRIPTION "Bacs Alarm Sensor Communication Lost ."
       ::= { bacsWellKnownAlarms  23 }

    bacsAlarmDischarging OBJECT-IDENTITY
       STATUS      current
       DESCRIPTION "Bacs Alarm Discharging ."
       ::= { bacsWellKnownAlarms  24 }

    bacsAlarmDischargingStopped OBJECT-IDENTITY
       STATUS      current
       DESCRIPTION "Bacs Alarm Discharging Stopped ."
       ::= { bacsWellKnownAlarms  25 }

    bacsAlarmMaxVoltageDiff OBJECT-IDENTITY
       STATUS      current
       DESCRIPTION "Bacs Alarm Max Voltage difference."
       ::= { bacsWellKnownAlarms  26 }

    bacsAlarmStringVoltHigh OBJECT-IDENTITY
       STATUS      current
       DESCRIPTION "Bacs Alarm String Voltage High."
       ::= { bacsWellKnownAlarms  27 }

    bacsAlarmStringVoltLow OBJECT-IDENTITY
       STATUS      current
       DESCRIPTION "Bacs Alarm String Voltage Low."
       ::= { bacsWellKnownAlarms  28 }

    bacsAlarmStringVoltHighWarn OBJECT-IDENTITY
       STATUS      current
       DESCRIPTION "Bacs Warning String Voltage High."
       ::= { bacsWellKnownAlarms  29 }

    bacsAlarmStringVoltLowWarn OBJECT-IDENTITY
       STATUS      current
       DESCRIPTION "Bacs Warning String Voltage Low."
       ::= { bacsWellKnownAlarms  30 }

    bacsAlarmStringCurrentHigh OBJECT-IDENTITY
       STATUS      current
       DESCRIPTION "Bacs Alarm String Current High."
       ::= { bacsWellKnownAlarms  31 }

    bacsAlarmStringCurrentLow OBJECT-IDENTITY
       STATUS      current
       DESCRIPTION "Bacs Alarm String Current Low."
       ::= { bacsWellKnownAlarms  32 }

    bacsAlarmStringCurrentHighWarn OBJECT-IDENTITY
       STATUS      current
       DESCRIPTION "Bacs Warning String Current High."
       ::= { bacsWellKnownAlarms  33 }

    bacsAlarmStringCurrentLowWarn OBJECT-IDENTITY
       STATUS      current
       DESCRIPTION "Bacs Warning String Current Low."
       ::= { bacsWellKnownAlarms  34 }

    bacsAlarmStringEqualizingDisabled OBJECT-IDENTITY
       STATUS      current
       DESCRIPTION "Bacs Warning String Equalizing Disabled."
       ::= { bacsWellKnownAlarms  35 }

    bacsAlarmStringCurrDeviationCharge OBJECT-IDENTITY
       STATUS      current
       DESCRIPTION "Bacs Alarm String Current Deviation during Charge."
       ::= { bacsWellKnownAlarms  36 }

    bacsAlarmStringCurrDeviationDischarge OBJECT-IDENTITY
       STATUS      current
       DESCRIPTION "Bacs Alarm String Current Deviation during Discharge."
       ::= { bacsWellKnownAlarms  37 }

    bacsAlarmStringCurrDeviationChargeWarn OBJECT-IDENTITY
       STATUS      current
       DESCRIPTION "Bacs Warning String Current Deviation during Charge."
       ::= { bacsWellKnownAlarms  38 }

    bacsAlarmStringCurrDeviationDischargeWarn OBJECT-IDENTITY
       STATUS      current
       DESCRIPTION "Bacs Warning String Current Deviation during Discharge."
       ::= { bacsWellKnownAlarms  39 }

    bacsModuleAlarmsPresent OBJECT-TYPE
       SYNTAX      Gauge32
       MAX-ACCESS  read-only
       STATUS      current
       DESCRIPTION "The number of BACS modules presently in an alarm state."
       ::= { bacsAlarms 4 }

    bacsModuleWarningsPresent OBJECT-TYPE
       SYNTAX      Gauge32
       MAX-ACCESS  read-only
       STATUS      current
       DESCRIPTION "The number of BACS modules presently in a warning state."
       ::= { bacsAlarms 5 }

   --
   -- BACS Traps
   --

   bacsTraps   OBJECT IDENTIFIER ::= { bacs2 4 }

   bacsTrapAlarmEntryAdded NOTIFICATION-TYPE
       OBJECTS { bacsAlarmId, bacsAlarmDescr }
       STATUS      current
       DESCRIPTION "This trap is sent upon a alarm in the system appears."
       ::= { bacsTraps 1 }

   bacsTrapAlarmEntryRemoved NOTIFICATION-TYPE
       OBJECTS { bacsAlarmId, bacsAlarmDescr }
       STATUS      current
       DESCRIPTION "This trap is sent upon a alarm in the system disappears."
       ::= { bacsTraps 2 }

   --
   -- GX_R_AUX.
   --
   -- 1.3.6.1.2.1.33.5(.5)
   gxRAUX   OBJECT IDENTIFIER ::= { bacs2 5 }

   gxRAUXCount OBJECT-TYPE
      SYNTAX      PositiveInteger
      MAX-ACCESS  read-only
      STATUS      current
      DESCRIPTION "Configured Number of currently connected GX_R_AUX devices."
      ::= { gxRAUX 1 }

   RauxValues ::= SEQUENCE {
      rauxIndex          PositiveInteger,
      rauxInput1         PositiveInteger,
      rauxInName1        DisplayString (SIZE (0..255)),
      rauxInput2         PositiveInteger,
      rauxInName2        DisplayString (SIZE (0..255)),
      rauxInput3         PositiveInteger,
      rauxInName3        DisplayString (SIZE (0..255)),
      rauxInput4         PositiveInteger,
      rauxInName4        DisplayString (SIZE (0..255)),
      rauxOutput1        PositiveInteger,
      rauxOutName1       DisplayString (SIZE (0..255)),
      rauxOutput2        PositiveInteger,
      rauxOutName2       DisplayString (SIZE (0..255)),
      rauxOutput3        PositiveInteger,
      rauxOutName3       DisplayString (SIZE (0..255)),
      rauxOutput4        PositiveInteger,
      rauxOutName4       DisplayString (SIZE (0..255))
   }

   rauxTable    OBJECT-TYPE
      SYNTAX      SEQUENCE OF RauxValues
      MAX-ACCESS  not-accessible
      STATUS      current
      DESCRIPTION "The list of GX_R_AUX values."
      ::= { gxRAUX 2 }

   rauxEntry  OBJECT-TYPE
      SYNTAX      RauxValues
      MAX-ACCESS  not-accessible
      STATUS      current
      DESCRIPTION "An entry containing information applicable to a particular GX_R_AUX device."
      INDEX       { rauxIndex }
      ::= { rauxTable 1 }
      -- 1.3.6.1.2.1.33.5.5.2.1
   
   rauxIndex  OBJECT-TYPE
      SYNTAX      PositiveInteger
      MAX-ACCESS  not-accessible
      STATUS      current
      DESCRIPTION "The GX_R_AUX identifier."
      ::= { rauxEntry 1 }
      -- 1.3.6.1.2.1.33.5.5.2.1.1
   
   rauxInput1     OBJECT-TYPE
      SYNTAX      INTEGER {
         normal(0),
         alarm(1)
      }
      MAX-ACCESS  read-only
      STATUS      current
      DESCRIPTION "Value of Input 1"
      ::= { rauxEntry 2 }
   
   rauxInName1    OBJECT-TYPE
      SYNTAX      DisplayString (SIZE (0..255))
      MAX-ACCESS  read-only
      STATUS      current
      DESCRIPTION "Name of Input 1"
      ::= { rauxEntry 3 }
   
   rauxInput2     OBJECT-TYPE
      SYNTAX      INTEGER {
         normal(0),
         alarm(1)
      }
      MAX-ACCESS  read-only
      STATUS      current
      DESCRIPTION "Value of Input 2"
      ::= { rauxEntry 4 }
   
   rauxInName2    OBJECT-TYPE
      SYNTAX      DisplayString (SIZE (0..255))
      MAX-ACCESS  read-only
      STATUS      current
      DESCRIPTION "Name of Input 2"
      ::= { rauxEntry 5 }
   
   rauxInput3     OBJECT-TYPE
      SYNTAX      INTEGER {
         normal(0),
         alarm(1)
      }
      MAX-ACCESS  read-only
      STATUS      current
      DESCRIPTION "Value of Input 3"
      ::= { rauxEntry 6 }
   
   rauxInName3    OBJECT-TYPE
      SYNTAX      DisplayString (SIZE (0..255))
      MAX-ACCESS  read-only
      STATUS      current
      DESCRIPTION "Name of Input 3"
      ::= { rauxEntry 7 }
   
   rauxInput4     OBJECT-TYPE
      SYNTAX      INTEGER {
         normal(0),
         alarm(1)
      }
      MAX-ACCESS  read-only
      STATUS      current
      DESCRIPTION "Value of Input 4"
      ::= { rauxEntry 8 }
   
   rauxInName4    OBJECT-TYPE
      SYNTAX      DisplayString (SIZE (0..255))
      MAX-ACCESS  read-only
      STATUS      current
      DESCRIPTION "Name of Input 4"
      ::= { rauxEntry 9 }

   rauxOutput1     OBJECT-TYPE
      SYNTAX      INTEGER {
         normal(0),
         alarm(1)
      }
      MAX-ACCESS  read-only
      STATUS      current
      DESCRIPTION "Value of Output 1"
      ::= { rauxEntry 10 }
   
   rauxOutName1    OBJECT-TYPE
      SYNTAX      DisplayString (SIZE (0..255))
      MAX-ACCESS  read-only
      STATUS      current
      DESCRIPTION "Name of Output 1"
      ::= { rauxEntry 11 }
      
   rauxOutput2     OBJECT-TYPE
      SYNTAX      INTEGER {
         normal(0),
         alarm(1)
      }
      MAX-ACCESS  read-only
      STATUS      current
      DESCRIPTION "Value of Output 2"
      ::= { rauxEntry 12 }
   
   rauxOutName2    OBJECT-TYPE
      SYNTAX      DisplayString (SIZE (0..255))
      MAX-ACCESS  read-only
      STATUS      current
      DESCRIPTION "Name of Output 2"
      ::= { rauxEntry 13 }
      
   rauxOutput3     OBJECT-TYPE
      SYNTAX      INTEGER {
         normal(0),
         alarm(1)
      }
      MAX-ACCESS  read-only
      STATUS      current
      DESCRIPTION "Value of Output 3"
      ::= { rauxEntry 14 }
   
   rauxOutName3    OBJECT-TYPE
      SYNTAX      DisplayString (SIZE (0..255))
      MAX-ACCESS  read-only
      STATUS      current
      DESCRIPTION "Name of Output 3"
      ::= { rauxEntry 15 }
      
   rauxOutput4     OBJECT-TYPE
      SYNTAX      INTEGER {
         normal(0),
         alarm(1)
      }
      MAX-ACCESS  read-only
      STATUS      current
      DESCRIPTION "Value of Output 4"
      ::= { rauxEntry 16 }
   
   rauxOutName4    OBJECT-TYPE
      SYNTAX      DisplayString (SIZE (0..255))
      MAX-ACCESS  read-only
      STATUS      current
      DESCRIPTION "Name of Output 4"
      ::= { rauxEntry 17 }

   END
